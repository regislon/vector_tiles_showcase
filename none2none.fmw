FME workspace none2none.fmw

Creator
    GEOMTYPE = Geometry Object
    NUM = 1
    CREATED -> FeatureReader [INITIATOR]
FeatureReader
    ATTRIBUTES = public.canton,"ogc_fid,uuid,datum_aend,datum_erst,erstell_j,erstell_m,revision_j,revision_m,grund_aend,herkunft,herkunft_j,herkunft_m,objektart,revision_q,icc,kantonsnum,see_flaech,kantonsfla,kt_teil,name,einwohnerz",public.communes,"ogc_fid,uuid,datum_aend,datum_erst,erstell_j,erstell_m,revision_j,revision_m,grund_aend,herkunft,herkunft_j,herkunft_m,objektart,bezirksnum,see_flaech,revision_q,name,kantonsnum,icc,einwohnerz,hist_nr,bfs_nummer,gem_teil,gem_flaech,shn"
    ATTR_ACCUM_MODE = Only Use Result
    COMBINE_GEOM = Use Result
    DATASET = localhost
    FEATURETYPES = public.canton public.communes
    FORMAT = POSTGIS
    INTERACT = NONE
    ORDER_RESULTS = No
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = localhost
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    public.canton -> FeatureWriter [public.canton]
    public.communes -> FeatureWriter_2 [public.canton]
FeatureWriter
    DATASET = $(FME_MF_DIR_ENCODED)temp/0-10.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 5
    MBTILES_MVT_MAX_FEATURES = 200000
    MBTILES_MVT_MAX_SIZE = 500000
    MBTILES_MVT_MINZOOM = 0
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
FeatureWriter_2
    DATASET = $(FME_MF_DIR_ENCODED)temp/10-18.mbtiles
    DATASET_ATTR = _dataset
    FEATURE_TYPE_LIST_ATTR = _feature_types
    FORMAT = MBTILES_MVT
    MBTILES_MVT_BUFFER_SIZE_CALCULATION = AUTO
    MBTILES_MVT_COORDINATE_SYSTEM_GRANULARITY = FEATURE
    MBTILES_MVT_DESTINATION_DATASETTYPE_VALIDATION = Yes
    MBTILES_MVT_EXTENT = 4096
    MBTILES_MVT_LAYER_TYPE = overlay
    MBTILES_MVT_MAXZOOM = 18
    MBTILES_MVT_MAX_FEATURES = 200000
    MBTILES_MVT_MAX_SIZE = 500000
    MBTILES_MVT_MINZOOM = 10
    MBTILES_MVT_OVERWRITE_DB = No
    MBTILES_MVT_SIMPLIFICATION = 0.0
    MBTILES_MVT_SIMPLIFICATION_MAX_ZOOM = 0.0
    MBTILES_MVT_WRITE_NULLS = YES
    TOTAL_FEATURES_WRITTEN_ATTR = _total_features_written
